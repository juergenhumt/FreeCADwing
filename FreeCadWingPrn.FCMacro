import FreeCAD
import Part
import TechDraw
import _pickle as pickle
from utilFCD2 import rdObjDat2

dataDir = '/home/jhumt/Flight/FreeCad/monoWing/data/'

prjFname  = 'prjData.dat'
prjFlName = dataDir + prjFname

firstrunDICT = True
if firstrunDICT:
  prjF = open(prjFlName,'rb')
  prjData = pickle.load(prjF)
  prjF.close()



# prjData={"prjName": prjName, "wkDir": wkDir, "datFlName": datFlName}
prjName = prjData["prjName"]
wkDir   = prjData["wkDir"]
datFlName = wkDir + prjData["datFlName"]


oF = open('out.lis','w')

docName2 = wkDir + prjName + ".FCStd"
App.openDocument(docName2)
doc = FreeCAD.activeDocument()
docName = prjName

objFlName = wkDir + 'obj' + prjName + '_mod.lis'
outStr='using objFlNam  ' + objFlName + '\n'
App.Console.PrintMessage(outStr)

objList = FreeCAD.ActiveDocument.Objects




objList = doc.Objects

# k= kNew

newDrwPg = 1
if newDrwPg > 0:
	# App.activeDocument().addObject('TechDraw::DrawPage', 'Page')
	doc.addObject('TechDraw::DrawPage', 'Page')	
	doc.addObject('TechDraw::DrawSVGTemplate', 'Template')
	doc.Template.Template = "/usr/share/freecad/Mod/TechDraw/Templates/A3_Landscape_blank.svg"
	doc.Page.Template = App.activeDocument().Template
	doc.recompute()

# in the first run set kB=1 and generate a list of all objects in the model
# open the file and select the ribs from tip to root one after another
# write consecutive numbers behind each objekt in the objcts9.lis file and
# save it as prnObjctsList9.lis. 
# for the second run set kB = -1. This second run places all ribs on an svg
# page. Unfortunately I did not find a way to assign the colour red rgb=FF0000
# to the rib contours so this has to be done manually if you want to generate
# an input File for a laser cutter

# fName = "/home/jhumt/Flight/FreeCad/monoWing/prnObjcts9.lis"
objNumLst = rdObjDat2(objFlName)

doc = FreeCAD.ActiveDocument
page = doc.getObject('Page')

vW  = "View00"
vNm = "View"

m=0
dY   = 20
dYsm =  0
xA   = 70  
dXa  = 3.5

for k in range(1,len(objNumLst)):
  view = doc.addObject("TechDraw::DrawViewPart", vNm)
  page.addView(view)
  view.Source = [objList[objNumLst[k][1]]]
  doc.getObject(vNm).Direction = (0, 0, 1)
  FreeCAD.getDocument(docName).getObject(vNm).XDirection = (0, 0, 1)
  FreeCAD.getDocument(docName).getObject(vNm).X = xA
  FreeCAD.getDocument(docName).getObject(vNm).Y = 245 - dYsm  # 380 - dYsm

  doc.commitTransaction()
  FreeCAD.getDocument(docName).getObject(vNm).recompute()
  
  m=m+1
  xA = xA + dXa
  dYsm = dYsm + dY + k

  if (k==9):
    xA = 250
    dXa  = 0 
    dYsm = -3
  

  if (k == 10):
    vW = "View0"
    dy = 10
  vNm = vW + str(k)
